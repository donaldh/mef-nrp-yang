module CoreModel-CoreFoundationModule-TypeDefinitions {
    namespace "uri:onf:CoreModel-CoreFoundationModule-TypeDefinitions";
    prefix CoreModel-CoreFoundationModule-TypeDefinitions;
    revision 2016-06-21{}
    typedef DateAndTime {
        type string;
    }
    typedef BitString {
        type string;
    }
    typedef Real {
        type string;
    }
    typedef PrintableString {
        type string;
    }
}
