module CoreModel-CoreModelEnhancements-InformationArchitectureAndPatterns {
    namespace "uri:onf:CoreModel-CoreModelEnhancements-InformationArchitectureAndPatterns";
    prefix CoreModel-CoreModelEnhancements-InformationArchitectureAndPatterns;
    revision 2016-06-21{}
    list Component {
        config true;
        ordered-by system;
        uses G_Component;
    }
    grouping G_Component {
        status deprecated;
        list _port {
            config true;
            ordered-by system;
            uses G_Port;
            min-elements 1;
        }
        list _attributePackageList {
            config true;
            ordered-by system;
            uses G_AttributePackage;
        }
        leaf _boundComponent {
            type leafref {
                path '/Component/undefined';
            }
        }
        leaf _encapsulatedSystem {
            type leafref {
                path '/CoreModel-CoreModelEnhancements-InformationArchitectureAndPatterns:System/CoreModel-CoreModelEnhancements-InformationArchitectureAndPatterns:undefined';
            }
        }
    }
    list Port {
        config true;
        ordered-by system;
        uses G_Port;
    }
    grouping G_Port {
        status deprecated;
        leaf Role {
            type string;
            default true;
        }
        leaf _boundPort {
            type leafref {
                path '/Port/undefined';
            }
        }
    }
    list System {
        config true;
        ordered-by system;
        uses G_System;
    }
    grouping G_System {
        status deprecated;
    }
    list AttributePackage {
        config true;
        ordered-by system;
        uses G_AttributePackage;
    }
    grouping G_AttributePackage {
        status deprecated;
    }
}
