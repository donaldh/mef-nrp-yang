module NetworkResource-Main-ObjectClasses {
    namespace "uri:onf:NetworkResource-Main-ObjectClasses";
    prefix NetworkResource-Main-ObjectClasses;
    import CoreModel-CoreModelEnhancements-ProfilesTemplatesAndSpecificationsModule {
        prefix CoreModel-CoreModelEnhancements-ProfilesTemplatesAndSpecificationsModule;
    }
    import NetworkResource-Main {
        prefix NetworkResource-Main;
    }
    revision 2016-06-21{}
    grouping G_CeLPSpec {
        uses CoreModel-CoreModelEnhancements-ProfilesTemplatesAndSpecificationsModule:G_LpSpec;
    }
    grouping G_CeTerminSpec {
        uses CoreModel-CoreModelEnhancements-ProfilesTemplatesAndSpecificationsModule:G_TerminationSpec;
    }
    grouping G_CeConnPtAndAdaptSpec {
        uses CoreModel-CoreModelEnhancements-ProfilesTemplatesAndSpecificationsModule:G_ConnectionPointAndAdapterSpec;
    }
    augment "/CoreModel-CoreModelEnhancements-ProfilesTemplatesAndSpecificationsModule:LtpSpec" {
        uses G_CeLtpSpec;
    }
    grouping G_CeLtpSpec {
        uses CoreModel-CoreModelEnhancements-ProfilesTemplatesAndSpecificationsModule:G_LtpSpec;
    }
    grouping G_CeEndPointLpSpec {
        uses G_CeLPSpec;
    }
    list CeSpUniLpPac {
        key 'uuid';
        config true;
        ordered-by system;
        uses G_CeSpUniLpPac;
    }
    grouping G_CeSpUniLpPac {
        leaf serviceProviderUniId {
            type string;
        }
        leaf maxFrameSize {
            type string;
        }
        leaf maxNumOfEvcs {
            type string;
        }
        leaf serviceMultiplexingEnabled {
            type boolean;
        }
        leaf bundlingEnabled {
            type boolean;
        }
        leaf allToOneBundlingEnabled {
            type boolean;
        }
        leaf untaggedAndPriorityTaggedCeVlanId {
            type string;
        }
        leaf l2cpAddressSet {
            type string;
        }
        leaf l2cpPeering {
            type string;
        }
        leaf tokenShareEnabled {
            type boolean;
        }
        leaf uuid {
            type string;
        }
    }
    list CeEvcEndPointLpSpec {
        key 'uuid';
        config true;
        uses G_CeEndPointLpSpec;
        leaf cosMappingType {
            type string;
        }
        leaf sourceMacAddressLimit {
            type string;
        }
        leaf eecMappingType {
            type string;
        }
        leaf aggLinkDepth {
            type string;
        }
        leaf evcEndPointMap {
            type string;
        }
        leaf subscriberMegMipEnabled {
            type boolean;
        }
        leaf testMegEnabled {
            type boolean;
        }
    }
    list CeEnniOvcEndPointLpSpec {
        key 'uuid';
        config true;
        uses G_CeEndPointLpSpec;
    }
    list CeUniOvcEndPoint {
        key 'uuid';
        config true;
        uses G_CeEndPointLpSpec;
    }
    list CeUniTerminSpec {
        key 'uuid';
        config true;
        uses G_CeTerminSpec;
        container _cespuniterminpac {
            config true;
            uses G_CeSpUniTerminPac;
        }
        container _ceopuniterminpac {
            config true;
            uses G_CeOpUniTerminPac;
        }
    }
    list CeSpUniTerminPac {
        key 'uuid';
        config true;
        ordered-by system;
        uses G_CeSpUniTerminPac;
    }
    grouping G_CeSpUniTerminPac {
        leaf uuid {
            type string;
        }
    }
    list CeOpUniTerminPac {
        key 'uuid';
        config true;
        ordered-by system;
        uses G_CeOpUniTerminPac;
    }
    grouping G_CeOpUniTerminPac {
        leaf uuid {
            type string;
        }
    }
    list CeUniConnPtAndAdaptSpec {
        key 'uuid';
        config true;
        uses G_CeConnPtAndAdaptSpec;
        container _cespuniconnptandadaptpac {
            config true;
            uses G_CeSpUniConnPtAndAdaptPac;
        }
        container _ceopuniconnptandadaptpac {
            config true;
            uses G_CeOpUniConnPtAndAdaptPac;
        }
    }
    list CeSpUniConnPtAndAdaptPac {
        key 'uuid';
        config true;
        ordered-by system;
        uses G_CeSpUniConnPtAndAdaptPac;
    }
    grouping G_CeSpUniConnPtAndAdaptPac {
        leaf uuid {
            type string;
        }
    }
    list CeOpUniConnPtAndAdaptPac {
        key 'uuid';
        config true;
        ordered-by system;
        uses G_CeOpUniConnPtAndAdaptPac;
    }
    grouping G_CeOpUniConnPtAndAdaptPac {
        leaf uuid {
            type string;
        }
    }
    list CeEvcEndPointConnPtAndAdaptSpec {
        key 'uuid';
        config true;
        uses G_CeEndPointConnPtAndAdaptSpec;
    }
    grouping G_CeEndPointConnPtAndAdaptSpec {
        uses G_CeConnPtAndAdaptSpec;
    }
    list CeEnniLpSpec {
        key 'uuid';
        config true;
        uses G_CeLPSpec;
    }
    list CeInniLpSpec {
        key 'uuid';
        config true;
        uses G_CeLPSpec;
    }
    list CeUniOvcEndPointConnPtAndAdaptSpec {
        key 'uuid';
        config true;
        uses G_CeEndPointConnPtAndAdaptSpec;
    }
    list CeEnniOvcEndPointConnPtAndAdaptSpec {
        key 'uuid';
        config true;
        uses G_CeEndPointConnPtAndAdaptSpec;
    }
    list CeUniLpSpec {
        key 'uuid';
        config true;
        uses G_CeLPSpec;
        container _cespunilppac {
            config true;
            uses G_CeSpUniLpPac;
        }
        container _ceopunilppac {
            config true;
            uses G_CeOpUniLpPac;
        }
        leaf elmiEnabled {
            type boolean;
        }
    }
    list CeOpUniLpPac {
        key 'uuid';
        config true;
        ordered-by system;
        uses G_CeOpUniLpPac;
    }
    grouping G_CeOpUniLpPac {
        leaf uuid {
            type string;
        }
    }
    list CeEtyAggrLpSpec {
        key 'uuid';
        config true;
        uses G_CeLPSpec;
        leaf-list phyTypePerLink {
            ordered-by system;
            type string;
        }
        leaf-list syncModePerLink {
            ordered-by system;
            type string;
            min-elements 1;
        }
        leaf numberOfLinks {
            type string;
        }
        leaf resiliencyOfLinks {
            type string;
        }
        leaf portConvsIdToAggLinkMap {
            type string;
        }
        leaf oamEnabledOnAllLinks {
            type boolean;
        }
        leaf megEnabledOnAllLinks {
            type boolean;
        }
    }
    grouping G_CeEvcFcPortSetSpec {
        uses G_CeFcPortSetSpec;
    }
    augment "/CoreModel-CoreModelEnhancements-ProfilesTemplatesAndSpecificationsModule:FcSpec" {
        uses G_CeFcSpec;
    }
    grouping G_CeFcSpec {
        uses CoreModel-CoreModelEnhancements-ProfilesTemplatesAndSpecificationsModule:G_FcSpec;
    }
    augment "/CoreModel-CoreModelEnhancements-ProfilesTemplatesAndSpecificationsModule:FcPortSetSpec" {
        uses G_CeFcPortSetSpec;
    }
    grouping G_CeFcPortSetSpec {
        uses CoreModel-CoreModelEnhancements-ProfilesTemplatesAndSpecificationsModule:G_FcPortSetSpec;
    }
    list CeEvcFcSpec {
        key 'uuid';
        config true;
        uses G_CeFcSpec;
    }
    list CeOvcSpec {
        key 'uuid';
        config true;
        uses G_CeFcSpec;
    }
    list CeOvcFcPortSetSpec {
        key 'uuid';
        config true;
        uses G_CeFcPortSetSpec;
    }
    list CeEthFrameAggregateLpSpec {
        key 'uuid';
        config true;
        uses G_CeLPSpec;
        leaf oamEnabled {
            type boolean;
        }
    }
    list CeEthFrameFlowLpSpec {
        key 'uuid';
        config true;
        uses G_CeLPSpec;
    }
    list CeEthFrameAggregateTerminSpec {
        key 'uuid';
        config true;
        uses G_CeTerminSpec;
    }
    list CeEthFrameAggregateConnPtAndAdaptSpec {
        key 'uuid';
        config true;
        uses G_CeConnPtAndAdaptSpec;
    }
    list CeEthFrameFlowConnPtAndAdaptLpSpec {
        key 'uuid';
        config true;
        uses G_CeConnPtAndAdaptSpec;
    }
    list CeEthFc {
        key 'uuid';
        config true;
        uses G_CeFcSpec;
        leaf connectionType {
            type string;
        }
        leaf unicastFrameDelivery {
            type string;
        }
        leaf multicastFrameDelivery {
            type string;
        }
        leaf broadcastFrameDelivery {
            type string;
        }
        leaf ceVlanIdPreservation {
            type string;
        }
        leaf ceVlanPcpPreservation {
            type boolean;
        }
        leaf ceVlanDeiPreservation {
            type boolean;
        }
        leaf maxNumOfEndPoint {
            type string;
        }
        container ceovc_pac {
            config true;
            uses NetworkResource-Main:G_CeOvc_Pac;
        }
    }
    grouping G_CeEthFcPortSetSpec {
        uses G_CeFcPortSetSpec;
    }
}
