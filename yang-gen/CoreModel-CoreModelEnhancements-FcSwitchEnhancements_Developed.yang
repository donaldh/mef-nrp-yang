module CoreModel-CoreModelEnhancements-FcSwitchEnhancements_Developed {
    namespace "uri:onf:CoreModel-CoreModelEnhancements-FcSwitchEnhancements_Developed";
    prefix CoreModel-CoreModelEnhancements-FcSwitchEnhancements_Developed;
    import CoreModel-CoreNetworkModule-ObjectClasses {
        prefix CoreModel-CoreNetworkModule-ObjectClasses;
    }
    revision 2016-06-21{}
    list ConfigurationGroup {
        status deprecated;
        config true;
        list _configurationAndSwitchControlRefList {
            description "A controller operating in the scope defined.";
            key 'uuid';
            config true;
            ordered-by system;
            uses CoreModel-CoreNetworkModule-ObjectClasses:G_ConfigurationAndSwitchController;
        }
    }
}
